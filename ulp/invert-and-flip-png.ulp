//Developed by Shohei Aoki, 2014
int res1 = system("/usr/local/bin/convert ~/Desktop/eagle_png/top.png -negate ~/Desktop/eagle_png/top-invert.png");
int res2 = system("/usr/local/bin/convert ~/Desktop/eagle_png/bottom.png -negate ~/Desktop/eagle_png/bottom-invert.png");
int res3 = system("/usr/local/bin/convert ~/Desktop/eagle_png/top-invert.png -flop ~/Desktop/eagle_png/top-invert-flop.png");
int res4 = system("/usr/local/bin/convert ~/Desktop/eagle_png/bottom-invert.png -flop ~/Desktop/eagle_png/bottom-invert-flop.png");
string errorMsg;
sprintf(errorMsg,"An error occured when inverting image. %d %d %d %d",res1,res2,res3,res4);
if (res1 == 0 && res2 == 0 && res3 ==0 && res4 == 0){
  dlgMessageBox("Image successfully inverted and flipped.");
} else {
  dlgMessageBox(errorMsg);
}
